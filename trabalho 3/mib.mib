-- Exemplo de MIB Simples
-- OID Base: 1.3.6.1.4.1.9999
EXEMPLO-MIB DEFINITIONS ::= BEGIN

--
-- Example MIB objects for agent module example implementations
--

IMPORTS
    MODULE-IDENTITY, OBJECT-TYPE, Integer32, Counter32, Gauge32, TimeTicks, 
    NOTIFICATION-TYPE                       FROM SNMPv2-SMI
    SnmpAdminString                         FROM SNMP-FRAMEWORK-MIB
    RowStatus, StorageType                  FROM SNMPv2-TC
    IpAddress                               FROM SNMPv2-SMI
    DisplayString                           FROM SNMPv2-TC
    MacAddress                              FROM SNMPv2-TC
;


-- Identificação da MIB
exemploModule MODULE-IDENTITY
    LAST-UPDATED "202311060000Z"
    ORGANIZATION "Sua Organizacao"
    CONTACT-INFO "email@exemplo.com"
    DESCRIPTION "MIB Simples de Exemplo"
    REVISION "202311060000Z"
    DESCRIPTION 
        "Primeira versao da MIB"
    ::= { 1 3 6 1 4 1 9999 }

exampleObjects OBJECT IDENTIFIER ::= { exemploModule 1 }

-- Defina seus objetos aqui
hostTable OBJECT-TYPE
    SYNTAX SEQUENCE OF HostEntry
    MAX-ACCESS not-accessible
    STATUS current
    DESCRIPTION
        "Tabela que armazena informacoes sobre hosts descobertos."
    ::= { exemploModule 2 }

hostEntry OBJECT-TYPE
    SYNTAX HostEntry
    MAX-ACCESS not-accessible
    STATUS current
    DESCRIPTION
        "Entrada para informacoes de um host."
    INDEX { hostIndex }
    ::= { hostTable 1 }

hostType OBJECT-TYPE
    SYNTAX DisplayString
    MAX-ACCESS read-only
    STATUS current
    DESCRIPTION
        "Tipo do host."
    ::= { hostEntry 7 }

discoveryTime OBJECT-TYPE
    SYNTAX SnmpAdminString
    MAX-ACCESS read-only
    STATUS current
    DESCRIPTION
        "Tempo de descoberta do host."
    ::= { hostEntry 6 }

hostName OBJECT-TYPE
    SYNTAX DisplayString
    MAX-ACCESS read-only
    STATUS current
    DESCRIPTION
        "Nome do host."
    ::= { hostEntry 2 }

hostIP OBJECT-TYPE
    SYNTAX IpAddress
    MAX-ACCESS read-only
    STATUS current
    DESCRIPTION
        "Endereco IP do host."
    ::= { hostEntry 3 }

hostMAC OBJECT-TYPE
    SYNTAX MacAddress
    MAX-ACCESS read-only
    STATUS current
    DESCRIPTION
        "Endereco MAC do host."
    ::= { hostEntry 4 }

hostManufacturer OBJECT-TYPE
    SYNTAX DisplayString
    MAX-ACCESS read-only
    STATUS current
    DESCRIPTION
        "Fabricante do host."
    ::= { hostEntry 5 }


hostIndex OBJECT-TYPE
    SYNTAX Integer32 (1..2147483647)
    MAX-ACCESS not-accessible
    STATUS current
    DESCRIPTION
        "Indice unico para identificar um host na tabela."
    ::= { hostEntry 1 }


HostEntry ::= SEQUENCE {
    hostIndex         Integer32,
    hostName          DisplayString,
    hostIP            IpAddress,
    hostMAC           MacAddress,
    hostManufacturer  DisplayString,
    discoveryTime     SnmpAdminString,
    hostType          DisplayString
}

-- Tipos adicionais
MacAddress ::= OCTET STRING (SIZE (6))

END
